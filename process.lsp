(defun cad:unlocked (data / layer flags)
  (setq layer (tblsearch "LAYER" (cdr (assoc 8 data))))
  (setq flags (cdr (assoc 70 layer)))
  (= 0 (logand 4 flags))
)
(defun cad:explode-ok (data / kind block flags)
  (setq kind (cdr (assoc 0 data)))
  (and (cad:unlocked data)
    (cond
      ((= kind "INSERT")
        (setq block (tblsearch "BLOCK" (cdr (assoc 2 data))))
        (setq flags (cdr (assoc 70 block)))
        (and (= 0 (logand flags 12)) (/= 1 (cdr (assoc 66 data)))))
      ((= kind "LWPOLYLINE") T)
      ((= kind "POLYLINE") (= 0 (logand 80 (cdr (assoc 70 data)))))
      (T nil)
    )
  )
)
(defun cad:run (/ *error* oldtab oldfile oldecho oldlayer pass ss i e data before skipped f output marker tab)
  (defun *error* (msg)
    (princ (strcat "\nCAD_BATCH_FAILED: " msg "\n"))
    (princ)
  )
  (setq output (getenv "CAD_BATCH_OUTPUT") marker (getenv "CAD_BATCH_MARKER"))
  (if (or (not output) (not marker) (findfile output))
    (progn (princ "\nCAD_BATCH_FAILED: Missing settings or existing output.\n") (exit)))
  (setq oldtab (getvar "CTAB") oldfile (getvar "FILEDIA") oldecho (getvar "CMDECHO") oldlayer (getvar "CLAYER"))
  (setvar "FILEDIA" 0)
  (setvar "CMDECHO" 0)
  (setq skipped 0)
  (foreach tab (cons "Model" (layoutlist))
    (setvar "CTAB" tab)
    (setq pass (atoi (getenv "CAD_BATCH_PASSES")))
    (repeat pass
      ; Refresh selection on EVERY pass: exploded entities have new handles.
      (setq ss (ssget "_X" (list (cons 410 tab))))
      (if ss
        (progn
          (setq i 0)
          (repeat (sslength ss)
            (setq e (ssname ss i) i (1+ i) data (entget e))
            (if (and data (cad:explode-ok data))
              (command-s "_.EXPLODE" e "")
            )
          )
        )
      )
    )
    (setq ss (ssget "_X" (list (cons 410 tab))))
    (if ss
      (progn
        (setq i 0)
        (repeat (sslength ss)
          (setq e (ssname ss i) i (1+ i) data (entget e))
          ; Keep remaining blocks/Xrefs/attributes intact rather than losing their meaning.
          (if (and data (cad:unlocked data) (/= "INSERT" (cdr (assoc 0 data))))
            (if (not (entmod (subst (cons 8 "0") (assoc 8 data) data))) (setq skipped (1+ skipped)))
            (setq skipped (1+ skipped))
          )
        )
      )
    )
  )
  (setvar "CTAB" oldtab)
  (setvar "CLAYER" oldlayer)
  ; PURGE removes only unused definitions. Never use destructive LAYDEL.
  (repeat 3 (command-s "_.-PURGE" "_All" "*" "_No"))
  (setvar "CMDECHO" oldecho)
  (command-s "_.SAVEAS" "_2004" output)
  (if (findfile output)
    (progn
      (setq f (open marker "w"))
      (write-line "CAD_BATCH_OK" f) (close f)
      (princ (strcat "\nCAD_BATCH_OK; preserved/skipped objects: " (itoa skipped) "\n"))
      (command-s "_.QUIT")
    )
    (princ "\nCAD_BATCH_FAILED: output missing.\n")
  )
  (princ)
)
